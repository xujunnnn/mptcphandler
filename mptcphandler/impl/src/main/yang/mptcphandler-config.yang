module mptcp-handler-config {

    yang-version 1;
    namespace "urn:opendaylight:packet:mptcp-handler-config";
    prefix "mptcp-handler-config";

    description
        "This module contains the base configuration for mptcphandler-impl
        implementation.";

    revision 2014-05-28 {
        description "Initial revision.";
    }

    container mptcp-handler-config {
        leaf mptcp-flow-table-id {
            type uint8;
            default 0;
        }
        leaf mptcp-flow-priority {
            type uint16;
            default 10;
        }
        leaf mptcp-flow-hard-timeout {
            type uint16;
            default 0;
        }
        leaf mptcp-flow-idle-timeout {
            type uint16;
            default 0;
     	}
		leaf mptcp-flow-vlan{
	    type uint8;
	    default 3;
		}
		leaf route-flow-priority {
            type uint16;
            default 10;
        }
        leaf route-flow-hard-timeout {
            type uint16;
            default 0;
        }
        leaf route-flow-idle-timeout {
            type uint16;
            default 0;
     	}
    }
}
